FME workspace csv2filegdb.fmw

Parameters:
- SourceDataset_CSV = $(FME_MF_DIR)outputCSV\formaAll_test.csv   # Source Comma Separated Value (CSV) File(s)
- DestDataset_FILEGDB = C:\Aamir\Temp\fromCSVTest.gdb   # Destination Geodatabase

Readers:
- CSV_1: CSV from $(SourceDataset_CSV)

Writers:
- FILEGDB_1: FILEGDB to $(DestDataset_FILEGDB) in LL84

CSV (reader CSV_1)
    attributes: UNIQUE_ID_STR char(24), UNIQUE_ID char(20), RES char(4), TILEH char(6), TILEV char(6), COL char(5), ROW char(5), LAT char(20), LON char(20), ISO3 char(5), PERC_TREE_COVER char(16), ADM_REGION char(11), ECO_REGION char(11), MATT_HANSEN_DEFOR char(18), PROBABILITY char(12), DATE_RECORDED char(14), DATE_INDEX char(11)
    -> 2DPointAdder
2DPointAdder
    XVALATTR = @Value(LON)
    YVALATTR = @Value(LAT)
    -> DateFormatter
DateFormatter
    DATE_ATTR = DATE_RECORDED
    FMT = FME Date/Time (%Y%m%d%H%M%S)
    -> CSV (writer FILEGDB_1)
CSV (writer FILEGDB_1)
    attributes: UNIQUE_ID_STR text(2048), UNIQUE_ID text(2048), RES text(2048), TILEH text(2048), TILEV text(2048), COL text(2048), ROW text(2048), LAT text(2048), LON text(2048), ISO3 text(2048), PERC_TREE_COVER text(2048), ADM_REGION text(2048), ECO_REGION text(2048), MATT_HANSEN_DEFOR text(2048), PROBABILITY text(2048), DATE_RECORDED text(2048), DATE_INDEX text(2048)
